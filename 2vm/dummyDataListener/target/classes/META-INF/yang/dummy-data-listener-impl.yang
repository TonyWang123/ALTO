module host-tracker-impl {

  yang-version 1;
  namespace "urn:opendaylight:alto:dummy-data-listener-impl";
  prefix "dummy-data-listener-impl";

  import config { prefix config; revision-date 2013-04-05; }
  import opendaylight-md-sal-binding { prefix mdsal; revision-date 2013-10-28; }

  description
    "This module contains the base YANG definitions for
    dummy-data-listener-impl implementation.";

  revision 2014-05-28 {
    description "Initial module draft.";
  }

  // This is the definition of the service implementation as a module identity.
  identity dummy-data-listener-impl {
    base config:module-type;

    // Specifies the prefix for generated java classes.
    config:java-name-prefix DummyDataListener;
  }

  // Augments the 'configuration' choice node under modules/module.
  // We consume the three main services, RPCs, DataStore, and Notifications
  augment "/config:modules/config:module/config:configuration" {
    case dummy-data-listener-impl {
      when "/config:modules/config:module/config:type = 'dummy-data-listener-impl'";

      container data-broker {
        uses config:service-ref {
          refine type {
            mandatory false;
            config:required-identity mdsal:binding-async-data-broker;
          }
        }
      }
    }
  }
}
