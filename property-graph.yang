module property-graph{
	yang-version 1;
	
	namespace "urn:ietf:params:xml:ns:yang:property-gragh";
	
	prefix "pg";
	
	import ietf-inet-types{
		prefix inet;
	}
	
	import alto-service{
		prefix as;
	}
	
	organization "Not Defined";
	contact "Not Defined";
	
	description 
		"This module defines a model for the property gragh 
		based on draft-yang-alto-topology-03.";
	
	
	typedef pid-name {
		type string {
		  length "1..64";
		  pattern "[0-9a-zA-Z_\-:@\.]+";
		}
		description
		  "Name for the PID." +
		  "RFC7285, Section 10.1. Note: the '.' separator MUST NOT be" +
		  "used unless specifically indicated in RFC7285 or an extension" +
		  "document.";
	}
	
	typedef cost-metric {
		type union {
		  type enumeration {
			enum routingcost {
			  value "0";
			  description
			  "Default metric. MUST support. RFC7285 Sec. 6.1.1.1.";
			}
			enum hopcount {
			  value "1";
			  description
			  "Hopcount metric.";
			}
		  }
		  type string {
			pattern "[\w\-:\.]+";
		  }
		}
		description
		  "Cost metric. 'priv:' reserved for Private Use.";
	}

	typedef cost-mode {
		type enumeration {
		  enum numerical {
			value "0";
			description
			  "Numerical cost mode.";
		  }
		  enum ordinal {
			value "1";
			description
			  "Ordinal cost mode.";
		  }
		  enum path-vector {
			value "2";
			description
				"Path-vector cost mode.";
		  }
		}
		description
		  "Cost mode. MUST support at least one of numerical and ordinal";
	}

	grouping cost-type {
		leaf cost-type-name {
		  type string;
		}
		leaf cost-mode {
		  type cost-mode;
		  description
			"Cost mode.";
		}
		leaf cost-metric {
		  type cost-metric;
		  description
			"Cost metric.";
		}
		leaf description {
		  type string;
		  description
			"Optional description field.";
		}
		description
		  "Cost type. RFC7285 Sec. 10.7." +
		  " object {
			  CostMetric cost-metric;
			  CostMode   cost-mode;
			  [JSONString description;]
			} CostType;";
	}
	
	grouping cost{
		leaf-list path-vector-cost{
			type string;
		}
	}
	
	container path-vector{
		leaf pid{
			type pid-name;
		}
	}
	
	grouping NetworkElementProperties{
		leaf bw{
			type string;
		}
		leaf-list srlg{
			type string;
		}
		description
			"draft-yang-alto-topology-03 sec.5" +
			"object-map {
				JSONString bw;
				JSONString srlg<0,*>;
			} NetworkElementProperties;";
	}
	
	grouping NetworkElementMapData{
		leaf element{
			type string;
		}
		uses NetworkElementProperties;
	}
	
	grouping cost-value{
		leaf metric{
			type cost-metric;
		}
		choice metric-type{
			case availbw{
				leaf availbw-value{
					type decimal64{
						fraction-digits 6;
					}
				}
			}
			case srlg{
				leaf-list srlg-value{
					type string;
				}
			}
		}
		description
			"draft-yang-alto-topology-03 sec.6" +
			"object {
				CostMetric metric;
				JSONValue value; // value type depends on metric type
			} CostValue;";
	}
	
	
	grouping link-properties{
		leaf src{
			type string;
		}
		leaf dst{
			type string;
		}
		leaf type{
			type string;
		}
		container costs{
			list cost-values{
				uses cost-value;
			}
		}
		description
			"draft-yang-alto-topology-03 sec.6" +
			"object {
				JSONString src;
				JSONString dst;
				JSONString type;
				CostValue costs<0,*>;
			} LinkProperties;";
	}
	
	grouping node-properties{
		leaf type{
			type string;
		}
		description
			"draft-yang-alto-topology-03 sec.6" +
			"object {
				JSONString type;
				...
			} NodeProperties;";
	}
	
	grouping NodeMapData{
		leaf node{
			type string;
		}
		uses node-properties;
		
		description
			"draft-yang-alto-topology-03 sec.6" +
			"object-map {
				JSONString -> NodeProperties;
			} NodeMapData;";
	}

	grouping LinkMapData{
		leaf link{
			type string;
		}
		uses link-properties;
		
		description
			"draft-yang-alto-topology-03 sec.6" +
			"object-map { 
				JSONString -> LinkProperties;
			 } LinkMapData;";
	}

	
	rpc path-vector-service{
		input{
			leaf request{
				type string;
			}
		}
		output{
			container meta{
				uses as:meta;
				container cost-type {
					uses cost-type;
					description
					  "Cost type.";
				}
			}
			list CostMapData{
				leaf src{
					type leafref{
						path "/path-vector/pid";
					}
				}
				key "src";
				list DstCosts{
					leaf dst{
						type leafref{
							path "/path-vector/pid";
						}
					}
					key "dst";
					uses cost;
				}
			}
		}
		description
			"draft-yang-alto-topology-03 sec.4" + 
			"object {
				cost-map.DstCosts.JSONValue -> JSONString<0,*>;
				meta.cost-mode = path-vector;
			} InfoResourcePVCostMap : InfoResourceCostMap;";
	}
	
	
	
	rpc network-element-property-map-service{
		input{
			leaf request{
				type string;
			}
		}
		output{
			container meta{
				uses as:meta;
			}
			list nep-map{
				uses NetworkElementMapData;
			}
		}
	}
			
	
	rpc node-edge-service{
		input{
			leaf request{
				type string;
			}
		}
		output{
			container meta{
				uses as:meta;
			}
			container topology-map{
				list nodes{
					uses NodeMapData;
				}
				list links{
					uses LinkMapData;
				}
			}
		}
	}
			
}
