module alto-service { /* test write */
  yang-version 1;
  
  namespace "urn:ietf:params:xml:ns:yang:alto-service";
  // TODO: replace with IANA namespace when assigned

  prefix "as";

  import ietf-inet-types {
    prefix inet;
  }

  /*
  // currently unused
  import ietf-yang-types {
    prefix yang;
  }
  */

  organization "TBD";
  contact "WILL-BE-DEFINED-LATER";

  description 
    "This module defines a model for the ALTO service
     based on draft-ietf-alto-protocol-27.";

  revision 2014-09-29 {
    description "v1. pending review";
  }

  revision 2014-09-24 {
    description "Initial revision. betw Michael and Xiao";
  }
  
  /* Type definitions */

  typedef endpoint-address {
    type union {
      type inet:ipv4-address;
      type inet:ipv6-address;
      // type TypedEndpointAddr;
    }
    description
      "Endpoint address, either IPv4 or Ipv6." +
      "or TypedEndpointAddr, see below.";
  }

  typedef TypedEndpointAddr {
    type string {
      pattern "[0-9a-zA-Z]+:.+";
    }
    description
      "Ref: RFC7285 Sec. 10.4.1 Typed Endpoint Addresses" +
      "= AddressType:EndpointAddr" +
      "TODO: restrict both halves of the address. See TODO.txt for" +
      "explanation of difficulty. The second half should extend the" +
      "restrictions if the first half (AddressType is ipv4 or" +
      "ipv6). Ref: RFC7285 10.4.2.";
  }

  typedef endpoint-address-type {
    type enumeration {
      enum ipv4;
      enum ipv6;
      enum MAC;
      enum overlay-ID;
      // put more options here;
    }
    description
      "If the address is not typed, it has an associated address type." +
      "Ref: RFC7285 Sec 2.2.";
  }
  
  typedef EndpointPrefix {
    type inet:ip-prefix;
  }
  
  grouping EndpointAddrGroup {
    description
      "EndpointAddrGroup. RFC7285 Sec. 10.4.5." +
      " object-map {
          AddressType -> EndpointPrefix<0..*>;
        } EndpointAddrGroup;";
    list endpoint-address-group {
      key AddressType;
      leaf AddressType {
        type endpoint-address-type;
      }
      leaf-list EndpointPrefix {
        type EndpointPrefix;
      }
      must
        "AddressType != 'ipv4' or " +
        "(AddressType = 'ipv4' and EndpointPrefix = 'inet:ipv4-prefix')" {
        error-message "Invalid ipv4 address.";
      }      
      must
        "AddressType != 'ipv6' or " +
        "(AddressType = 'ipv6' and EndpointPrefix = 'inet:ipv6-prefix')" {
        error-message "Invalid ipv6 address.";
      }
    }
  }

  grouping endpoint-addresses {
    leaf-list endpoints {
      type endpoint-address;
      description
        "The leaf list identifies endpoints.";
    }
  }

  typedef network-location {
    type union {
      type inet:ipv4-prefix;
      type inet:ipv6-prefix;
      type inet:ipv4-address;
      type inet:ipv6-address;
    }
    description
      "Network location, either IPv4 or Ipv6.";
  }

  grouping network-locations {
    leaf-list locations {
      type network-location;
      description
        "The leaf list identifies network locations.";
    }
    description
      "This corresponds to the term __Network Location__ in RFC7285 Sec. 2.3";
  }

  typedef pid-name {
    type string {
      length "1..64";
      pattern "[0-9a-zA-Z_\-:@\.]+";
    }
    description
      "Name for the PID." +
      "RFC7285, Section 10.1. Note: the '.' separator MUST NOT be" +
      "used unless specifically indicated in RFC7285 or an extension" +
      "document.";
  }

  typedef cost-metric {
    type union {
      type enumeration {
        enum routingcost {
          value "0";
          description
          "Default metric. MUST support. RFC7285 Sec. 6.1.1.1.";
        }
        enum hopcount {
          value "1";
          description
          "Hopcount metric.";
        }
      }
      type string {
        pattern "[\w\-:\.]+";
      }
    }
    description
      "Cost metric. 'priv:' reserved for Private Use.";
  }

  typedef cost-mode {
    type enumeration {
      enum numerical {
        value "0";
        description
          "Numerical cost mode.";
      }
      enum ordinal {
        value "1";
        description
          "Ordinal cost mode.";
      }
    }
    description
      "Cost mode. MUST support at least one of numerical and ordinal";
  }

  grouping cost-type {
    leaf cost-type-name {
      type string;
    }
    leaf cost-mode {
      type cost-mode;
      description
        "Cost mode.";
    }
    leaf cost-metric {
      type cost-metric;
      description
        "Cost metric.";
    }
    leaf description {
      type string;
      description
        "Optional description field.";
    }
    description
      "Cost type. RFC7285 Sec. 10.7." +
      " object {
          CostMetric cost-metric;
          CostMode   cost-mode;
          [JSONString description;]
        } CostType;";
  }

  typedef endpoint-property-type {
    type enumeration {
      enum resource-specific-endpoint-property;
      enum global-endpoint-property;
    }
    description
      "Endpoint property type. RFC7285 Sec. 10.8.";
  }

  typedef resource-specific-endpoint-property {
    type string {
      length "3..97"; //len(resource-id) + 1 + len(global-property)
      pattern "[\w\-:@\.]+\.[\w\-:_]+"; // resource-id.property
    }
    description
      "Resource-specific endpoint property.";
  }

  typedef global-endpoint-property {
    type union {
      type enumeration {
        enum pid {
          value "0";
          description "PID property.";
        }
        enum network-location {
          value "1";
          description
            "Network location";
        }
        // other examples here
      }
      type string {
        length "1..32";
        pattern "[\w\-:_]+"; // '.' is not allowed.
      }
    }
    description
      "Global endpoint property. RFC7285 Sec. 10.8.2." +
      "'priv:' for Private Use ";
  }

  typedef endpoint-property {
    type union {
      type resource-specific-endpoint-property;
      type global-endpoint-property;
    }
    description
      "Endpoint property (value). RFC7285 Sec. 10.8";
  }

  typedef resource-id {
    type pid-name;
    description
      "Resource-ID.";
  }

  grouping version-tag {
    leaf resource-id {
      type resource-id;
    }
    leaf tag {
      type string {
        length "1..64";
      }
      description
        "Tag.";
    }
    description
      "Version tag. Both resource-id and tag must be equal
       byte-for-byte. RFC7285 Sec. 10.3." +
      " object {
          ResourceID resource-id;
          JSONString tag;
        } VersionTag;";
  }

  grouping meta {
    choice dependent {
      mandatory true;
      // multiple vtags
      case dependent {
        list vtags {
          uses version-tag;
          description
            "Version tags.";
        }
      }
      case independent {
        container vtag {
          uses version-tag;
          description
            "Version tag.";
        }
      }
    }
    description
      "Meta information. RFC7285 Sec. 8.4.1." + 
      "object-map { JSONString -> JSONValue } ResponseMeta;";
  }

  typedef media-type {
    type union {
      type string {
        // TODO: restrict more? RFC 7285, Sec. 14.1?
        pattern "application/alto\-.*";
      }
      type enumeration {
        enum alto-directory+json;
        enum alto-networkmap+json;
        enum alto-networkmapfilter+json;
        enum alto-costmap+json;
        enum alto-costmapfilter+json;
        enum alto-endpointprop+json;
        enum alto-endpointpropparams+json;
        enum alto-endpointcost+json;
        enum alto-endpointcostparams+json;
        enum alto-error+json;
      }
    }
  }    
      
  grouping network-map {
    container meta {
      uses meta;
    }
    list pids {
      key "pid";
      leaf pid {
        type pid-name;
      }
      uses EndpointAddrGroup;
      description
        "RFC7285 Sec. 11.2.1.6." + 
        " object-map {
            PIDName -> EndpointAddrGroup;
          } NetworkMapData;";
    }
    description
      "Network map. RFC7285 Sec. 11.2.1.6." +
      "object {
         NetworkMapData network-map;
       } InfoResourceNetworkMap : ResponseEntityBase;";
  }

  typedef alto-cost {
    type decimal64 {
      fraction-digits 6;
    }
    description
      "ALTO costs, currently only integer values.";
  }

  grouping cost-map {
    container meta {
      uses meta;
      container cost-type {
        uses cost-type;
        description
          "Cost type.";
      }
    }
    list CostMapData {
      leaf src {
        type pid-name;
        description
          "Source PID.";
      }
      key "src";
      list DstCosts {
        leaf dst {
          type pid-name;
          description
            "Destination PID.";
        }
        key "dst";
        leaf cost {
          type alto-cost;
          description
            "Cost from source to destination.";
        }
        description
          "The list represents the inner part of the cost matrix." +
          "DstCosts. RFC7285 Sec. 11.2.3.6." +
          " object-map {
              PIDName -> JSONValue;
            } DstCosts;";
      }         
      description
        "The list represents the outer part of the cost matrix." +
        "CostMapData. RFC7285 Sec. 11.2.3.6." +
        " object-map {
            PIDName -> DstCosts;
          } CostMapData;";
    }
    leaf accepts {
      type media-type;
    }
    container capabilities {
      leaf-list cost-type-names {
        type leafref {
          path "../../meta/cost-type/cost-type-name";
        }
        min-elements 1;
        max-elements 1;
      }
      leaf-list prop-types {
        type endpoint-property;
      }
      description
        "CostMapCapabilities. RFC7285 Sec. 11.2.3.4." +
        " object {
            JSONString cost-type-names<1..1>;
          } CostMapCapabilities;";
      // TODO: model other CostMapCapabilities, if provided
    }
    leaf-list uses {
      type resource-id;
    }
    description
      "Cost map. RFC7285 Sec. 11.2.3.6." +
      " object {
          CostMapData cost-map;
        } InfoResourceCostMap : ResponseEntityBase;";
  }

  /* Instances */

  container map-service {
    config false;
    list network-map {
      key "resource-id";
      leaf resource-id {
        type leafref {
          path "../../../IRD/IRD-resource-entries/resource-id";
        }
      }
      uses network-map;
      description
        "Network map service (unfiltered).";
    }
    list cost-map {
      key "resource-id";
      leaf resource-id {
        type leafref {
          path "../../../IRD/IRD-resource-entries/resource-id";
        }
      }
      uses cost-map;
      description
        "Cost map service (unfiltered).";
    }
    description
      "Network and cost map service (unfiltered).";
  }

  container IRD {
    container IRD-resource-entries {
      leaf resource-id {
        type resource-id;
      }
      container IRD-resource-entry {
        leaf uri {
          type inet:uri;
        }
        leaf media-type {
          type media-type;
        }
        leaf accepts {
          type media-type;
        }
        container capabilities {
          list cost-type-names {
            uses cost-type;
            key cost-type-name;
          }
        }
        leaf-list uses {
          type resource-id;
        }
        description
          "IRDResourceEntry. RFC7285 9.2.2." +
          " object {
              JSONString      uri;
              JSONString      media-type;
              [JSONString     accepts;]
              [Capabilities   capabilities;]
              [ResourceID     uses<0..*>;]
            } IRDResourceEntry;";
      }
      description
        "IRDResourceEntries. RFC7285 9.2.2." +
        " object-map {
            ResourceID  -> IRDResourceEntry;
          } IRDResourceEntries;";
    }
    description
      "InformationResourceDirectory. RFC7285 9.2.2." +
      " object {
          IRDResourceEntries resources;
        } InfoResourceDirectory : ResponseEntityBase;";
  }

  // RPCs
  rpc endpoint-cost-service {
    input {
      container cost-type {
        uses cost-type;
        description
          "Cost type.";
      }
      leaf-list constraints {
        type string;
      }
      container endpoints {
        container srcs {
          uses endpoint-addresses;
          description
            "Source endpoint addresses.";
        }
        container dsts {
          uses endpoint-addresses;
          description
            "Destination endpoint addresses.";
        }
        description
          "Endpoint addresses. RFC7285 Sec. 11.5.1.3." +
          " object {
              [TypedEndpointAddr srcs<0..*>;]
              [TypedEndpointAddr dsts<0..*>;]
            } EndpointFilter;";
      }
      description
        "Request for cost map (unfiltered). RFC7285 Sec. 11.5.1.3." +
        " object {
            CostType          cost-type;
            [JSONString       constraints<0..*>;]
            EndpointFilter    endpoints;
          } ReqEndpointCostMap;";
    }
    output {
      container meta {
        uses meta;
        // uses augment to add cost-type fields
        description
          "Meta information.";
      }
      container endpoint-cost-map {
        list srcs {
          key "src";
          leaf src {
            type endpoint-address;
            description
              "Source endpoint address.";
          }
          list dsts {
            key "dst";
            leaf dst {
              type endpoint-address;
              description
                  "Destination endpoint address.";
            }
            leaf cost {
              type alto-cost;
                description
                  "Cost from source to destination.";
            }
            description
              "The list represents the inner part of the cost matrix." +
              "RFC7285 Sec. 11.5.1.6." +
              " object-map {
                  TypedEndpointAddr -> JSONValue;
                } EndpointDstCosts;";
          }
          description
            "The list represents the outer part of the cost matrix." +
            "RFC7285 Sec. 11.5.1.6." +
            " object-map {
                TypedEndpointAddr -> EndpointDstCosts;
              } EndpointCostMapData;";
        }
        description
          "Endpoint-cost-map." +
          "RFC7285 Sec. 11.5.1.6." +
          " object {
              EndpointCostMapData endpoint-cost-map;
            } InfoResourceEndpointCostMap : ResponseEntityBase;";
      }
    }
  }

  rpc endpoint-property-service {
    description
      "inquiries on properties of an endpoint";
    input {
      container ReqEndpointProp {
        leaf-list endpoints {
          type endpoint-address;
          min-elements 1;
        }
        leaf-list properties {
          type endpoint-property-type;
          min-elements 1;
        }
        description
          " object {
              EndpointPropertyType  properties<1..*>;
              TypedEndpointAddr     endpoints<1..*>;
            } ReqEndpointProp;";
      }
    }
    output {
      container meta {
        uses meta;
      }
      list endpoint-properties {
        key pid;
        leaf pid {
          type endpoint-address;
        }
        list properties {
          key property-type;
          leaf property-type {
            type endpoint-property-type;
          }
          leaf property {
            type endpoint-property;
          }
          description
            "EndpointProps. RFC7285 Sec. 11.4.1.6." +
            " object {
                EndpointPropertyType -> JSONValue;
              } EndpointProps;";
        }
        description
          "EndpointPropertyMapData. Sec. 11.4.1.6." +
          " object-map {
              TypedEndpointAddr -> EndpointProps;
            } EndpointPropertyMapData;";
      }
      leaf-list capabilities {
        type endpoint-property-type;
        min-elements 1;
        description
          "Sec. 11.4.1.4." +
          " object {
              EndpointPropertyType prop-types<1..*>;
            } EndpointPropertyCapabilities;";
      }
      description
        "InfoResourceEndpointProperties. Sec. 11.4.1.6." +
        " object {
            EndpointPropertyMapData endpoint-properties;
          } InfoResourceEndpointProperties : ResponseEntityBase;";
    }
  }
  
  rpc filtered-network-map-service {
    description
      "inquiries on filtered network map";
    input {
      container ReqFilteredNetworkMap {
        leaf-list pids {
          type endpoint-address;
        }
        leaf-list address-types {
          type endpoint-address-type;
        }
        description
          "ReqFilteredNetworkMap. RFC7285 Sec. 11.3.1.3." +
          " object {
              PIDName pids<0..*>;
              [AddressType address-types<0..*>;]
            } ReqFilteredNetworkMap;";
      }
    }
    output {
      container meta {
        uses meta;
      }
      list network-map {
        key pid;
        leaf pid {
          type endpoint-address;
          description
            "must be present in the input srcs or dsts";
        }
        uses EndpointAddrGroup;
        description
          "RFC7285 Sec. 11.2.1.6." + 
          " object-map {
              PIDName -> EndpointAddrGroup;
            } NetworkMapData;";
      }
      description
        " object {
            NetworkMapData network-map;
          } InfoResourceNetworkMap : ResponseEntityBase;";
    }
  }

  rpc filtered-endpoint-cost-service {
    input {
      container ReqFilteredCostMap {
        container cost-type {
          uses cost-type;
          description
            "Cost type.";
        }
        leaf-list constraints {
          type string;
        }
        container pids {
          container srcs {
            uses endpoint-addresses;
            description
              "Source endpoint addresses.";
          }
          container dsts {
            uses endpoint-addresses;
            description
              "Destination endpoint addresses.";
          }
          description
            "PIDFilter: Endpoint addresses. RFC7285 Sec. 11.3.2.3." +
            " object {
                PIDName srcs<0..*>;
                PIDName dsts<0..*>;
              } PIDFilter;";
        }
        // TODO: optional constraint JSON strings RFC7285 Sec. 11.3.2.3
        description
          "ReqFilteredCostMap. RFC7285 Sec. 11.3.2.3." +
          " object {
              CostType   cost-type;
              [JSONString constraints<0..*>;]
              [PIDFilter  pids;]
            } ReqFilteredCostMap;";
      }
    }
    output {
      container meta {
        uses meta;
        description
          "Meta information.";
      }
      container cost-map {
        list CostMapData {
          leaf src {
            type endpoint-address;
            description
              "Source endpoint address.";
          }
          key "src";
          list DstCosts {
            leaf dst {
              type endpoint-address;
              description
                  "Destination endpoint address.";
            }
            key "dst";
            leaf cost {
              type alto-cost;
                description
                  "Cost from source to destination.";
            }
            description
              "The list represents the inner part of the cost matrix." +
              "DstCosts. RFC7285 Sec. 11.2.3.6." +
              " object-map {
                  PIDName -> JSONValue;
                } DstCosts;";
          }
          description
            "The list represents the outer part of the cost matrix." +
            "CostMapData. RFC7285 Sec. 11.2.3.6." +
            " object-map {
                PIDName -> DstCosts;
              } CostMapData;";
        }
        description
          "Endpoint-cost-map.";
      }
      container capabilities {
        leaf-list cost-type-names {
          type leafref {
            path "../../meta/cost-type/cost-type-name";
          }
          min-elements 1;
        }
        leaf cost-constraints {
          type boolean;
        }
        description
          "FilteredCostMapCapabilities. RFC7285 Sec. 11.3.2.4." +
          " object {
              JSONString cost-type-names<1..*>;
              JSONBool cost-constraints;
            } FilteredCostMapCapabilities;";
      // TODO: model other CostMapCapabilities, if provided
      }
    }
  }

  augment "/endpoint-cost-service/output/meta" {
    container cost-type {
      uses cost-type;
      description
        "Cost type. MUST be included. RFC7285 Sec. 11.5.1.6";
    }
  }

  augment "/filtered-endpoint-cost-service/output/meta" {
    container cost-type {
      uses cost-type;
      description
        "Cost type. MUST be included. RFC7285 Sec. 11.5.1.6";
    }
  }

  augment "/IRD-request/output/meta" {
    list cost-types {
      key "cost-type-name";
      uses cost-type;
      description
        "Cost type. RFC7285 Sec. 9.2.2." + 
        " object-map {
            JSONString -> CostType;
          } IRDMetaCostTypes;";
    }
    leaf default-alto-network-map {
      type leafref {
        path "../../../../IRD/IRD-resource-entries/resource-id";
      }
    }
  }

  rpc IRD-request {
    input {
      // TODO: change this
      leaf request {
        type string;
      }
    }
    output {
      container meta {
        uses meta;
      }
      list resources  {
        key "resource-id";
        leaf resource-id {
          /*type leafref {
            path "/IRD/IRD-resource-entries/resource-id";
          }*/
          type resource-id;
        }
        leaf uri {
          type inet:uri;
        }
        leaf media-type {
          type media-type;
        }
        leaf accepts {
          type media-type;
        }
        container capabilities {
          leaf cost-constraints {
            type boolean;
          }
          leaf-list cost-type-names {
            type leafref {
              path "/map-service/cost-map/capabilities/cost-type-names";
            }
          }
          leaf-list prop-types {
            type leafref {
              path "/map-service/cost-map/capabilities/prop-types";
            }
          }
        }
        leaf-list uses {
          type leafref {
            path "/map-service/cost-map/uses";
          }
        }
        description
        "IRDResourceEntry. RFC7285 9.2.2." +
        " object {
            JSONString      uri;
            JSONString      media-type;
            [JSONString     accepts;]
            [Capabilities   capabilities;]
            [ResourceID     uses<0..*>;]
          } IRDResourceEntry;" +
        "IRDResourceEntries. RFC7285 9.2.2." +
        " object-map {
            ResourceID  -> IRDResourceEntry;
          } IRDResourceEntries;";
      }
      description
        "InformationResourceDirectory. RFC7285 9.2.2." +
        " object {
            IRDResourceEntries resources;
          } InfoResourceDirectory : ResponseEntityBase;";
    }
  }

}
